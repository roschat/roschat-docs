MINICOM-MIB DEFINITIONS ::= BEGIN
  

IMPORTS
  enterprises
    FROM RFC1155-SMI;



  -- MINICOM Corparative branch

minicom OBJECT IDENTIFIER ::= { enterprises 34078 }

  -- Registration branch

minicomReg OBJECT IDENTIFIER ::= { minicom 1 }

  -- Experimental branch

minicomExp OBJECT IDENTIFIER ::= { minicom 2 }

  -- Extensions branch

minicomExt OBJECT IDENTIFIER ::= { minicom 3 }

  -- Proprientary branch

minicomProp OBJECT IDENTIFIER ::= { minicom 4 }

  -- DX500 branch

upats   OBJECT IDENTIFIER ::= { minicomProp 1 }
  -- TETRA branch

tetra   OBJECT IDENTIFIER ::= { minicomProp 2 }

  -- SWITCH branch

switch  OBJECT IDENTIFIER ::= { minicomProp 3 }

  -- MX1000 branch

ipats   OBJECT IDENTIFIER ::= { minicomProp 4 }

  -- voip branch

voip    OBJECT IDENTIFIER ::= { minicomProp 5 }

  -- roschat branch

roschat OBJECT IDENTIFIER ::= { minicomProp 6 }

END
